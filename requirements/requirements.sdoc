[DOCUMENT]
TITLE: Rustdoc Deploy Strictdoc test

[SECTION]
TITLE: Functional Requirements

[REQUIREMENT]
UID: REQ-1
TITLE: Requirement 1
STATEMENT: >>>
The code shall be clean
<<<
RATIONALE: >>>
The code shall be clean becaue XYZ
<<<

[REQUIREMENT]
UID: REQ-3
TITLE: Requirement 3
STATEMENT: >>>
The code shall be made from pure, good magic
<<<
RATIONALE: >>>
The code shall be made from pure magic because XYZ and ABC. The magic must be good!!!
<<<

[REQUIREMENT]
UID: REQ-5
TITLE: Requirement 5
STATEMENT: >>>
The code elves shall be happy
<<<
RATIONALE: >>>
You don't want to make the code elves unhappy, do you?
<<<
COMMENT: >>>
This is a comment
<<<

[/SECTION]
